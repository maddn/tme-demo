module tme-demo {

  yang-version 1.1;
  namespace "http://example.com/tme-demo";
  prefix tme-demo;

  include common-topology;
  include common-topology-ui;

  import ietf-inet-types {
    prefix inet;
  }
  import tailf-common {
    prefix tailf;
  }
  import tailf-ncs {
    prefix ncs;
  }
  import l3vpn {
    prefix l3vpn;
  }

  // NEDs
  import netsim-ned-cisco-ios {
    prefix ios;
  }
  import netsim-ned-cisco-ios-xr {
   prefix cisco-ios-xr;
  }
  import netsim-ned-juniper-junos {
    prefix junos;
  }
  import netsim-ned-alu-sr {
    prefix alu;
  }
  import netsim-ned-cisco-nx {
    prefix nx;
  }
  import netsim-ned-dell-ftos {
    prefix force10;
  }

  // NED IDs
  import cisco-ios-netsim-cli {
    prefix ios-ned-id;
  }
  import cisco-iosxr-netsim-cli {
   prefix iosxr-ned-id;
  }
  import juniper-junos-netsim-nc {
    prefix junos-ned-id;
  }
  import alu-sr-netsim-cli {
    prefix alu-ned-id;
  }
  import cisco-nx-netsim-cli {
    prefix nx-ned-id;
  }
  import dell-ftos-netsim-cli {
    prefix force10-ned-id;
  }

  identity l3vpn {
    base ncs:plan-component-type;
    description "L3VPN plan component";
  }

  identity data-centre {
    base ncs:plan-component-type;
    description "Data-centre plan component";
  }

  container topologies {
    uses assistant-settings-grouping;

    uses topology-grouping {
      augment "topology/devices" {
        list device {
          key device-name;

          leaf device-name {
            type leafref {
              path "/ncs:devices/ncs:device/ncs:name";
            }
            description "NSO device name displayed by the topology UI.";
          }
          uses topology-device-ui-grouping;
        }
      }

      augment "topology/links/link" {
        leaf link-vlan {
          type uint32;
        }

        container a-end-interface {
          leaf name {
            type string;
          }

          leaf ip-address {
            type tailf:ip-address-and-prefix-length;
          }
        }

        container z-end-interface {
          leaf name {
            type string;
          }

          leaf ip-address {
            type tailf:ip-address-and-prefix-length;
          }
        }
      }

      augment "topology" {
        uses topology-layout-grouping;
      }
    }
  }

  grouping interface-leafrefs-grouping {
    choice interface-type {
      leaf ios-GigabitEthernet{
        when "derived-from(/ncs:devices/ncs:device" +
             "[ncs:name=current()/../device]/ncs:device-type" +
             "/ncs:cli/ncs:ned-id, 'ios-ned-id:cisco-ios-netsim-cli')";
        tailf:info "Cisco IOS Gigabit Ethernet interface";
        type leafref {
          path "deref(../device)/../ncs:config" +
               "/ios:interface/ios:GigabitEthernet/ios:name";
        }
      }
      leaf ios-xr-GigabitEthernet {
        when "derived-from(/ncs:devices/ncs:device" +
             "[ncs:name=current()/../device]/ncs:device-type" +
             "/ncs:cli/ncs:ned-id, 'iosxr-ned-id:cisco-iosxr-netsim-cli')";
        tailf:info "Cisco IOS-XR Gigabit Ethernet interface";
        type leafref {
          path "deref(../device)/../ncs:config" +
               "/cisco-ios-xr:interface" +
               "/cisco-ios-xr:GigabitEthernet/cisco-ios-xr:id";
        }
      }
      leaf ios-xr-TenGigE {
        when "derived-from(/ncs:devices/ncs:device" +
             "[ncs:name=current()/../device]/ncs:device-type" +
             "/ncs:cli/ncs:ned-id, 'iosxr-ned-id:cisco-iosxr-netsim-cli')";
        tailf:info "Cisco IOS-XR 10 Gigabit Ethernet interface";
        type leafref {
          path "deref(../device)/../ncs:config" +
               "/cisco-ios-xr:interface" +
               "/cisco-ios-xr:TenGigE/cisco-ios-xr:id";
        }
      }
      leaf junos-interface {
        when "derived-from(/ncs:devices/ncs:device" +
             "[ncs:name=current()/../device]/ncs:device-type" +
             "/ncs:netconf/ncs:ned-id, 'junos-ned-id:juniper-junos-netsim-nc')";
        tailf:info "Junos interface";
        type leafref {
          path "deref(../device)/../ncs:config/junos:configuration" +
               "/junos:interfaces/junos:interface/junos:name";
        }
      }
      leaf alu-interface {
        when "derived-from(/ncs:devices/ncs:device" +
             "[ncs:name=current()/../device]/ncs:device-type" +
             "/ncs:cli/ncs:ned-id, 'alu-ned-id:alu-sr-netsim-cli')";
        tailf:info "ALU interface";
        type leafref {
          path "deref(../device)/../ncs:config/alu:port/alu:port-id";
        }
      }
      leaf nx-Ethernet {
        when "derived-from(/ncs:devices/ncs:device" +
             "[ncs:name=current()/../device]/ncs:device-type" +
             "/ncs:cli/ncs:ned-id, 'nx-ned-id:cisco-nx-netsim-cli')";
        tailf:info "Cisco NX Ethernet interface";
        type leafref {
          path "deref(../device)/../ncs:config/nx:interface" +
               "/nx:Ethernet/nx:name";
        }
      }
      leaf nx-port-channel {
        when "derived-from(/ncs:devices/ncs:device" +
             "[ncs:name=current()/../device]/ncs:device-type" +
             "/ncs:cli/ncs:ned-id, 'nx-ned-id:cisco-nx-netsim-cli')";
        tailf:info "Cisco NX Port Channel interface";
        type leafref {
          path "deref(../device)/../ncs:config/nx:interface" +
               "/nx:port-channel/nx:name";
        }
      }
      leaf f10-GigabitEthernet {
        when "derived-from(/ncs:devices/ncs:device" +
             "[ncs:name=current()/../device]/ncs:device-type" +
             "/ncs:cli/ncs:ned-id, 'force10-ned-id:dell-ftos-netsim-cli')";
        tailf:info "Dell Force10 GigabitEthernet interface";
        type leafref {
          path "deref(../device)/../ncs:config/force10:interface" +
               "/force10:GigabitEthernet/force10:id";
        }
      }
    }
  }

  container tme-demo {
    list tenant {
      key name;
      leaf name {
        tailf:info "Unique service id";
        tailf:cli-allow-range;
        type string;
      }

      description "Tenant";
      uses ncs:plan-data;
      uses ncs:service-data;
      ncs:servicepoint tme-demo-servicepoint;

      container l3vpn {
        tailf:info "Layer3 VPN parameters";
        presence true;

        leaf route-distinguisher {
          tailf:info "Route distinguisher/target identifier unique for the VPN";
          type uint32 {
            range "0..65535";
          }
          default 65535;
        }

        leaf qos-policy {
          tailf:info "VPN QoS Policy";
          type leafref {
            path "/l3vpn:qos/l3vpn:qos-policy/l3vpn:name";
          }
        }

        list endpoint {
          key "id";
          leaf id{
            tailf:info "Endpoint identifier";
            type string;
          }

          leaf ce-device {
            tailf:info "CE endpoint device";
            type leafref {
              path "/ncs:devices/ncs:device/ncs:name";
            }
            must "/ncs:devices/ncs:device-group[ncs:name='C']" +
                 "/ncs:device-name[.=current()]" {
              error-message "The device must be in the C device group";
            }
            must "count(/tme-demo:topologies/tme-demo:topology" +
                 "/tme-demo:links/tme-demo:link" +
                 "[tme-demo:a-end-device=current()])>0 or " +
                 "count(/tme-demo:topologies/tme-demo:topology" +
                 "/tme-demo:links/tme-demo:link" +
                 "[tme-demo:z-end-device=current()])>0" {
              error-message "The device must have a topology connection";
            }
            mandatory true;
          }

          leaf ce-interface {
            tailf:info "CE local GigabitEthernet interface";
            type leafref {
              path "deref(../ce-device)/../ncs:config" +
                   "/ios:interface/ios:GigabitEthernet/ios:name";
            }
            default "0/1";
          }

          leaf ip-network {
            tailf:info "CE interface local private network";
            type inet:ip-prefix;
            default "10.0.0.0/24";
          }

          leaf bandwidth {
            tailf:info "Endpoint bandwidth in bps";
            type uint32;
            default 10000000;
          }

          leaf as-number {
            tailf:info "CE device AS Number";
            type uint32 {
              range "0..65535";
            }
            default 500;
          }
        }
      }

      container data-centre {
        tailf:info "Data centre connectivity parameters";
        presence true;

        leaf vlan {
          tailf:info "Data centre tenant VLAN";
          type uint32;
          default 500;
        }

        leaf ip-network {
          tailf:info "The private IP network";
          type inet:ip-prefix;
          default "50.0.0.0/24";
        }

        leaf preserve-vlan-tags {
          type boolean;
          default false;
        }

        list endpoint {
          key "device compute";

          leaf device {
            tailf:info "TOR switch";
            type leafref {
              path "/ncs:devices/ncs:device/ncs:name";
            }
          }

          leaf compute {
            tailf:info "Compute node (not used)";
            type enumeration {
              enum compute0;
              enum compute1;
              enum compute2;
              enum compute3;
              enum compute4;
            }
          }

          uses interface-leafrefs-grouping;

          leaf connect-multiple-vlans {
            tailf:info "Make the accessport a trunk";
            type boolean;
            default false;
          }
        }
      }

      leaf touch-date {
        type string;
      }
    }
  }

  augment "/ncs:devices/ncs:device" {
    uses get-configuration-action-grouping;
  }

}
